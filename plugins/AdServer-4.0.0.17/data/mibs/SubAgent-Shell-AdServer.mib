SubAgent-Shell-AdServer-MIB DEFINITIONS ::= BEGIN

IMPORTS
  MODULE-IDENTITY, OBJECT-TYPE, Integer32 FROM SNMPv2-SMI
  monitoring FROM AdServer-MIB;

adsPollerInfo OBJECT IDENTIFIER ::= { monitoring 1 }

profilingRequestUrl OBJECT-TYPE
  SYNTAX OCTET STRING
  MAX-ACCESS read-only
  STATUS current
  DESCRIPTION "Monitoring profiling request url"
  ::= { monitoring 95 }

profilingRequestExecStatus OBJECT-TYPE
  SYNTAX Integer32
  MAX-ACCESS read-only
  STATUS current
  DESCRIPTION "Monitoring profiling request processing status"
  ::= { monitoring 96 }

profilingRequestExecTime OBJECT-TYPE
  SYNTAX OCTET STRING
  MAX-ACCESS read-only
  STATUS current
  DESCRIPTION "Time of monitoring profiling request processing in mseconds"
  ::= { monitoring 97 }

adRequestUrl OBJECT-TYPE
  SYNTAX OCTET STRING
  MAX-ACCESS read-only
  STATUS current
  DESCRIPTION "monitoring ad request url"
  ::= { monitoring 99 }

adRequestExecTime OBJECT-TYPE
  SYNTAX OCTET STRING
  MAX-ACCESS read-only
  STATUS current
  DESCRIPTION "Time of monitoring ad request processing in mseconds"
  ::= { monitoring 100 }

adRequestExecStatus OBJECT-TYPE
  SYNTAX Integer32
  MAX-ACCESS read-only
  STATUS current
  DESCRIPTION "Monitoring ad request processing status"
  ::= { monitoring 101 }

bidRequestUrl OBJECT-TYPE
  SYNTAX OCTET STRING
  MAX-ACCESS read-only
  STATUS current
  DESCRIPTION "monitoring bid request curl command"
  ::= { monitoring 110 }

bidRequestExecTime OBJECT-TYPE
  SYNTAX OCTET STRING
  MAX-ACCESS read-only
  STATUS current
  DESCRIPTION "Time of monitoring bid request processing in mseconds"
  ::= { monitoring 111 }

bidRequestExecStatus OBJECT-TYPE
  SYNTAX Integer32
  MAX-ACCESS read-only
  STATUS current
  DESCRIPTION "Monitoring bid request status"
  ::= { monitoring 112 }


apacheStatusEntry OBJECT IDENTIFIER ::= { monitoring 102 }
logfilesCountersEntry OBJECT IDENTIFIER ::= { monitoring 200 }
connectionsStatesEntry OBJECT IDENTIFIER ::= { monitoring 300 }

adsFunctionsCount  OBJECT-TYPE
  SYNTAX      Integer32
  MAX-ACCESS  read-only
  STATUS      current
  DESCRIPTION
  "Number of executed functions"
  ::= { adsPollerInfo 1 }

adsFunctionsSuccessCount  OBJECT-TYPE
  SYNTAX      Integer32
  MAX-ACCESS  read-only
  STATUS      current
  DESCRIPTION
  "Number of successfully executed functions"
  ::= { adsPollerInfo 2 }

adsFunctionsFailedCount  OBJECT-TYPE
  SYNTAX      Integer32
  MAX-ACCESS  read-only
  STATUS      current
  DESCRIPTION
  "Number of failed functions"
  ::= { adsPollerInfo 3 }

adsTimeStamp  OBJECT-TYPE
  SYNTAX      OCTET STRING
  MAX-ACCESS  read-only
  STATUS      current
  DESCRIPTION
  "Timestamp of last execution"
  ::= { adsPollerInfo 4 }
 
adsTotalExecTime  OBJECT-TYPE
  SYNTAX      OCTET STRING
  MAX-ACCESS  read-only
  STATUS      current
  DESCRIPTION
  "Total execution time"
  ::= { adsPollerInfo 5 }

END
