PassbackStat-MIB DEFINITIONS ::= BEGIN

IMPORTS
  MODULE-IDENTITY, OBJECT-TYPE, Unsigned32 FROM SNMPv2-SMI
  DisplayString FROM SNMPv2-TC
  logGeneralizer FROM LogGeneralizer-MIB;

passbackStat OBJECT IDENTIFIER ::= { logGeneralizer 120 }

inputTimeAvg OBJECT-TYPE
  SYNTAX DisplayString (SIZE(0..32))
  MAX-ACCESS read-only
  STATUS current
  DESCRIPTION "Average time spent on processing the input directory"
  ::= { passbackStat 1 }

inputTimeMax OBJECT-TYPE
  SYNTAX DisplayString (SIZE(0..32))
  MAX-ACCESS read-only
  STATUS current
  DESCRIPTION "Max time spent on processing the input directory"
  ::= { passbackStat 2 }

inputTimeTotal OBJECT-TYPE
  SYNTAX DisplayString (SIZE(0..32))
  MAX-ACCESS read-only
  STATUS current
  DESCRIPTION "Total time spent on processing the input directory"
  ::= { passbackStat 3 }

inputTimePerFileAvg OBJECT-TYPE
  SYNTAX DisplayString (SIZE(0..32))
  MAX-ACCESS read-only
  STATUS current
  DESCRIPTION "Average time spent on processing an input file"
  ::= { passbackStat 4 }

inputTimePerFileMax OBJECT-TYPE
  SYNTAX DisplayString (SIZE(0..32))
  MAX-ACCESS read-only
  STATUS current
  DESCRIPTION "Max time spent on processing an input file"
  ::= { passbackStat 5 }

inputSuccessCount OBJECT-TYPE
  SYNTAX Unsigned32
  MAX-ACCESS read-only
  STATUS current
  DESCRIPTION "Total number of successfully processed input files"
  ::= { passbackStat 6 }

inputErrorCount OBJECT-TYPE
  SYNTAX Unsigned32
  MAX-ACCESS read-only
  STATUS current
  DESCRIPTION "Total number of input files that the service has failed to process"
  ::= { passbackStat 7 }

outputTimeAvg OBJECT-TYPE
  SYNTAX DisplayString (SIZE(0..32))
  MAX-ACCESS read-only
  STATUS current
  DESCRIPTION "Average time spent on writing log data to disk or database"
  ::= { passbackStat 8 }

outputTimeMax OBJECT-TYPE
  SYNTAX DisplayString (SIZE(0..32))
  MAX-ACCESS read-only
  STATUS current
  DESCRIPTION "Max time spent on writing log data to disk or database"
  ::= { passbackStat 9 }

outputTimeTotal OBJECT-TYPE
  SYNTAX DisplayString (SIZE(0..32))
  MAX-ACCESS read-only
  STATUS current
  DESCRIPTION "Total time spent on writing log data to disk or database"
  ::= { passbackStat 10 }

outputRecordsAvg OBJECT-TYPE
  SYNTAX DisplayString (SIZE(0..32))
  MAX-ACCESS read-only
  STATUS current
  DESCRIPTION "Average number of log data records written per operation"
  ::= { passbackStat 11 }

outputRecordsMax OBJECT-TYPE
  SYNTAX Unsigned32
  MAX-ACCESS read-only
  STATUS current
  DESCRIPTION "Max number of log data records written per operation"
  ::= { passbackStat 12 }

outputRecordsTotal OBJECT-TYPE
  SYNTAX Unsigned32
  MAX-ACCESS read-only
  STATUS current
  DESCRIPTION "Total number of log data records written"
  ::= { passbackStat 13 }

outputSuccessCount OBJECT-TYPE
  SYNTAX Unsigned32
  MAX-ACCESS read-only
  STATUS current
  DESCRIPTION "Total number of successful write operations"
  ::= { passbackStat 14 }

outputErrorCount OBJECT-TYPE
  SYNTAX Unsigned32
  MAX-ACCESS read-only
  STATUS current
  DESCRIPTION "Total number of failed write operations"
  ::= { passbackStat 15 }

END
