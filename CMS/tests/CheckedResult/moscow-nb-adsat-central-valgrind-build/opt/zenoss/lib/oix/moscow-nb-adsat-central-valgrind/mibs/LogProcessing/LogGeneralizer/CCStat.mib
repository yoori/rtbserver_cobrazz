CCStat-MIB DEFINITIONS ::= BEGIN

IMPORTS
  MODULE-IDENTITY, OBJECT-TYPE, Unsigned32 FROM SNMPv2-SMI
  DisplayString FROM SNMPv2-TC
  logGeneralizer FROM LogGeneralizer-MIB;

ccStat OBJECT IDENTIFIER ::= { logGeneralizer 117 }

inputTimeAvg OBJECT-TYPE
  SYNTAX DisplayString (SIZE(0..32))
  MAX-ACCESS read-only
  STATUS current
  DESCRIPTION "Average time spent on processing the input directory"
  ::= { ccStat 1 }

inputTimeMax OBJECT-TYPE
  SYNTAX DisplayString (SIZE(0..32))
  MAX-ACCESS read-only
  STATUS current
  DESCRIPTION "Max time spent on processing the input directory"
  ::= { ccStat 2 }

inputTimeTotal OBJECT-TYPE
  SYNTAX DisplayString (SIZE(0..32))
  MAX-ACCESS read-only
  STATUS current
  DESCRIPTION "Total time spent on processing the input directory"
  ::= { ccStat 3 }

inputTimePerFileAvg OBJECT-TYPE
  SYNTAX DisplayString (SIZE(0..32))
  MAX-ACCESS read-only
  STATUS current
  DESCRIPTION "Average time spent on processing an input file"
  ::= { ccStat 4 }

inputTimePerFileMax OBJECT-TYPE
  SYNTAX DisplayString (SIZE(0..32))
  MAX-ACCESS read-only
  STATUS current
  DESCRIPTION "Max time spent on processing an input file"
  ::= { ccStat 5 }

inputSuccessCount OBJECT-TYPE
  SYNTAX Unsigned32
  MAX-ACCESS read-only
  STATUS current
  DESCRIPTION "Total number of successfully processed input files"
  ::= { ccStat 6 }

inputErrorCount OBJECT-TYPE
  SYNTAX Unsigned32
  MAX-ACCESS read-only
  STATUS current
  DESCRIPTION "Total number of input files that the service has failed to process"
  ::= { ccStat 7 }

outputTimeAvg OBJECT-TYPE
  SYNTAX DisplayString (SIZE(0..32))
  MAX-ACCESS read-only
  STATUS current
  DESCRIPTION "Average time spent on writing log data to disk or database"
  ::= { ccStat 8 }

outputTimeMax OBJECT-TYPE
  SYNTAX DisplayString (SIZE(0..32))
  MAX-ACCESS read-only
  STATUS current
  DESCRIPTION "Max time spent on writing log data to disk or database"
  ::= { ccStat 9 }

outputTimeTotal OBJECT-TYPE
  SYNTAX DisplayString (SIZE(0..32))
  MAX-ACCESS read-only
  STATUS current
  DESCRIPTION "Total time spent on writing log data to disk or database"
  ::= { ccStat 10 }

outputRecordsAvg OBJECT-TYPE
  SYNTAX DisplayString (SIZE(0..32))
  MAX-ACCESS read-only
  STATUS current
  DESCRIPTION "Average number of log data records written per operation"
  ::= { ccStat 11 }

outputRecordsMax OBJECT-TYPE
  SYNTAX Unsigned32
  MAX-ACCESS read-only
  STATUS current
  DESCRIPTION "Max number of log data records written per operation"
  ::= { ccStat 12 }

outputRecordsTotal OBJECT-TYPE
  SYNTAX Unsigned32
  MAX-ACCESS read-only
  STATUS current
  DESCRIPTION "Total number of log data records written"
  ::= { ccStat 13 }

outputSuccessCount OBJECT-TYPE
  SYNTAX Unsigned32
  MAX-ACCESS read-only
  STATUS current
  DESCRIPTION "Total number of successful write operations"
  ::= { ccStat 14 }

outputErrorCount OBJECT-TYPE
  SYNTAX Unsigned32
  MAX-ACCESS read-only
  STATUS current
  DESCRIPTION "Total number of failed write operations"
  ::= { ccStat 15 }

END
