StatsCollector-MIB DEFINITIONS ::= BEGIN

IMPORTS
  MODULE-IDENTITY, OBJECT-TYPE, Unsigned32, Counter64 FROM SNMPv2-SMI
  DisplayString FROM SNMPv2-TC
  controlling FROM AdServer-MIB;

  statsCollector OBJECT IDENTIFIER ::= { controlling 1 }

  historyMatch-Count OBJECT-TYPE
    SYNTAX Unsigned32
    MAX-ACCESS read-only
    STATUS current
    DESCRIPTION "Count of  UserInfo matching"
    ::= { statsCollector 1 }

  historyMatch-Total OBJECT-TYPE
    SYNTAX DisplayString (SIZE(0..32))
    MAX-ACCESS read-only
    STATUS current
    DESCRIPTION "Total time of UserInfo matching "
    ::= { statsCollector 2 }

  historyMatch-Max OBJECT-TYPE
    SYNTAX DisplayString (SIZE(0..32))
    MAX-ACCESS read-only
    STATUS current
    DESCRIPTION "Maximun time of UserInfo matching "
    ::= { statsCollector 3 }

  historyMatch-Min OBJECT-TYPE
    SYNTAX DisplayString (SIZE(0..32))
    MAX-ACCESS read-only
    STATUS current
    DESCRIPTION "Minimum time of UserInfo matching "
    ::= { statsCollector 4 }

  HistoryMatch-Average OBJECT-TYPE
    SYNTAX DisplayString (SIZE(0..32))
    MAX-ACCESS read-only
    STATUS current
    DESCRIPTION "Average time of Userinfo matching"
    ::= { statsCollector 5 }

  usersMerge-Count OBJECT-TYPE
    SYNTAX Unsigned32
    MAX-ACCESS read-only
    STATUS current
    DESCRIPTION "Count of UserInfo merging"
    ::= { statsCollector 6 }

  usersMerge-Total OBJECT-TYPE
    SYNTAX DisplayString (SIZE(0..32))
    MAX-ACCESS read-only
    STATUS current
    DESCRIPTION "Total time of UserInfo merging "
    ::= { statsCollector 7 }

  usersMerge-Max OBJECT-TYPE
    SYNTAX DisplayString (SIZE(0..32))
    MAX-ACCESS read-only
    STATUS current
    DESCRIPTION "Maximun time of UserInfo merging "
    ::= { statsCollector 8 }

  usersMerge-Min OBJECT-TYPE
    SYNTAX DisplayString (SIZE(0..32))
    MAX-ACCESS read-only
    STATUS current
    DESCRIPTION "Minimum time of UserInfo merging "
    ::= { statsCollector 9 }

  UsersMerge-Average OBJECT-TYPE
    SYNTAX DisplayString (SIZE(0..32))
    MAX-ACCESS read-only
    STATUS current
    DESCRIPTION "Average time of Userinfo merging"
    ::= { statsCollector 10 }

  triggersMatch-Count OBJECT-TYPE
    SYNTAX Unsigned32
    MAX-ACCESS read-only
    STATUS current
    DESCRIPTION "Count of triggers matching"
    ::= { statsCollector 11 }

  triggersMatch-Total OBJECT-TYPE
    SYNTAX DisplayString (SIZE(0..32))
    MAX-ACCESS read-only
    STATUS current
    DESCRIPTION "Total time of triggers matching "
    ::= { statsCollector 12 }

  triggersMatch-Max OBJECT-TYPE
    SYNTAX DisplayString (SIZE(0..32))
    MAX-ACCESS read-only
    STATUS current
    DESCRIPTION "Maximun time of triggers matching "
    ::= { statsCollector 13 }

  triggersMatch-Min OBJECT-TYPE
    SYNTAX DisplayString (SIZE(0..32))
    MAX-ACCESS read-only
    STATUS current
    DESCRIPTION "Minimum time of triggers matching "
    ::= { statsCollector 14 }

  triggersMatch-Average OBJECT-TYPE
    SYNTAX DisplayString (SIZE(0..32))
    MAX-ACCESS read-only
    STATUS current
    DESCRIPTION "Average time of triggers matching"
    ::= { statsCollector 15 }

  adRequest-Count OBJECT-TYPE
    SYNTAX Unsigned32
    MAX-ACCESS read-only
    STATUS current
    DESCRIPTION "Count of queries with defined tid"
    ::= { statsCollector 16 }

  campaignSelect-OptInUser-Count OBJECT-TYPE
    SYNTAX Unsigned32
    MAX-ACCESS read-only
    STATUS current
    DESCRIPTION "Count of optin users"
    ::= { statsCollector 17 }

  campaignSelect-OptOutUser-Count OBJECT-TYPE
    SYNTAX Unsigned32
    MAX-ACCESS read-only
    STATUS current
    DESCRIPTION "Count of optout users"
    ::= { statsCollector 18 }

  userProfiles OBJECT-TYPE
    SYNTAX Unsigned32
    MAX-ACCESS read-only
    STATUS current
    DESCRIPTION "Count users uid"
    ::= { statsCollector 19 }

  dailyUsers-Count OBJECT-TYPE
    SYNTAX Unsigned32
    MAX-ACCESS read-only
    STATUS current
    DESCRIPTION "Count daily users"
    ::= { statsCollector 20 }

  userBaseProfiles-AreaSize OBJECT-TYPE
    SYNTAX Counter64
    MAX-ACCESS read-only
    STATUS current
    DESCRIPTION "Space used by base profiles"
    ::= { statsCollector 21 }

  userTempProfiles-AreaSize OBJECT-TYPE
    SYNTAX Counter64
    MAX-ACCESS read-only
    STATUS current
    DESCRIPTION "Space used by temporary profiles"
    ::= { statsCollector 22 }

  userAdditionalProfiles-AreaSize OBJECT-TYPE
    SYNTAX Counter64
    MAX-ACCESS read-only
    STATUS current
    DESCRIPTION "Space used by addative profiles"
    ::= { statsCollector 23 }

  userHistoryProfiles-AreaSize OBJECT-TYPE
    SYNTAX Counter64
    MAX-ACCESS read-only
    STATUS current
    DESCRIPTION "Space used by history profiles"
    ::= { statsCollector 24 }

  userFreqCapProfiles-AreaSize OBJECT-TYPE
    SYNTAX Counter64
    MAX-ACCESS read-only
    STATUS current
    DESCRIPTION "Space used by freq cap profiles"
    ::= { statsCollector 25 }

  userWDProfiles-AreaSize OBJECT-TYPE
    SYNTAX Counter64
    MAX-ACCESS read-only
    STATUS current
    DESCRIPTION "Space used by wd impression profiles"
    ::= { statsCollector 26 }

  userProfiles-AreaSize OBJECT-TYPE
    SYNTAX Counter64
    MAX-ACCESS read-only
    STATUS current
    DESCRIPTION "Space used by profiles"
    ::= { statsCollector 27 }

  userProfiles-AdChannels-Avg OBJECT-TYPE
    SYNTAX DisplayString (SIZE(0..32))
    MAX-ACCESS read-only
    STATUS current
    DESCRIPTION "Average number of Ad Channels in User Profile"
    ::= { statsCollector 28 }

  userProfiles-DiscoverChannels-Avg OBJECT-TYPE
    SYNTAX DisplayString (SIZE(0..32))
    MAX-ACCESS read-only
    STATUS current
    DESCRIPTION "Average number of Discover Channels in User Profile"
    ::= { statsCollector 29 }

  adRequestWithImpression-OptInUser-Count OBJECT-TYPE
    SYNTAX Unsigned32
    MAX-ACCESS read-only
    STATUS current
    DESCRIPTION "Ad request from opted in users"
    ::= { statsCollector 30 }

  adRequestWithImpression-nonOptInUser-Count OBJECT-TYPE
    SYNTAX Unsigned32
    MAX-ACCESS read-only
    STATUS current
    DESCRIPTION "Ad request from opted out users"
    ::= { statsCollector 31 }

  adRequestWithPassback-OptInUser-Count OBJECT-TYPE
    SYNTAX Unsigned32
    MAX-ACCESS read-only
    STATUS current
    DESCRIPTION "Count passback queries from opted in users"
    ::= { statsCollector 32 }

  adRequestWithPassback-nonOptInUser-Count OBJECT-TYPE
    SYNTAX Unsigned32
    MAX-ACCESS read-only
    STATUS current
    DESCRIPTION "Count passbacks queries from opted out users"
    ::= { statsCollector 33 }

  actionRequest-OptInUser-Count OBJECT-TYPE
    SYNTAX Unsigned32
    MAX-ACCESS read-only
    STATUS current
    DESCRIPTION "Count action queries from opted in users"
    ::= { statsCollector 34 }

  actionRequest-nonOptInUser-Count OBJECT-TYPE
    SYNTAX Unsigned32
    MAX-ACCESS read-only
    STATUS current
    DESCRIPTION "Count action queries from opted out users"
    ::= { statsCollector 35 }

  discoverRequest-OptInUser-Count OBJECT-TYPE
    SYNTAX Unsigned32
    MAX-ACCESS read-only
    STATUS current
    DESCRIPTION "Count discovery queries from opted in users"
    ::= { statsCollector 36 }

  discoverRequest-nonOptInUser-Count OBJECT-TYPE
    SYNTAX Unsigned32
    MAX-ACCESS read-only
    STATUS current
    DESCRIPTION "Count discovery queries from opted out users"
    ::= { statsCollector 37 }

  ooRequest-InOp-Count OBJECT-TYPE
    SYNTAX Unsigned32
    MAX-ACCESS read-only
    STATUS current
    DESCRIPTION "Count opt in operations"
    ::= { statsCollector 38 }

  ooRequest-OutOp-Count OBJECT-TYPE
    SYNTAX Unsigned32
    MAX-ACCESS read-only
    STATUS current
    DESCRIPTION "Count opt out operations"
    ::= { statsCollector 39 }

  ooRequest-StatusOp-Count OBJECT-TYPE
    SYNTAX Unsigned32
    MAX-ACCESS read-only
    STATUS current
    DESCRIPTION "Count status operations"
    ::= { statsCollector 40 }

  profilingRequest-Count OBJECT-TYPE
    SYNTAX Unsigned32
    MAX-ACCESS read-only
    STATUS current
    DESCRIPTION "Total profiling requests"
    ::= { statsCollector 41 }

  profilingRequest-ReceivedTriggers-Count OBJECT-TYPE
    SYNTAX Unsigned32
    MAX-ACCESS read-only
    STATUS current
    DESCRIPTION "Total received triggers"
    ::= { statsCollector 42 }

  profilingRequest-MatchedTriggers-Count OBJECT-TYPE
    SYNTAX Unsigned32
    MAX-ACCESS read-only
    STATUS current
    DESCRIPTION "Total matched triggers"
    ::= { statsCollector 43 }

  profilingRequest-TriggeredChannels-Count OBJECT-TYPE
    SYNTAX Unsigned32
    MAX-ACCESS read-only
    STATUS current
    DESCRIPTION "Total matched channels"
    ::= { statsCollector 44 }

  passbackRequest-Count OBJECT-TYPE
    SYNTAX Unsigned32
    MAX-ACCESS read-only
    STATUS current
    DESCRIPTION "Count of passback queries"
    ::= { statsCollector 45 }

  campaignSelect-ProbeUser-Count OBJECT-TYPE
    SYNTAX Unsigned32
    MAX-ACCESS read-only
    STATUS current
    DESCRIPTION "Count of campagin selection for probe users"
    ::= { statsCollector 46 }

  campaignSelect-TemporaryUser-Count OBJECT-TYPE
    SYNTAX Unsigned32
    MAX-ACCESS read-only
    STATUS current
    DESCRIPTION "Count of campagin selection for temporary users"
    ::= { statsCollector 47 }

  campaignSelect-UndefinedUser-Count OBJECT-TYPE
    SYNTAX Unsigned32
    MAX-ACCESS read-only
    STATUS current
    DESCRIPTION "Count of campagin selection for undefined users"
    ::= { statsCollector 48 }

  requestParsing-Count OBJECT-TYPE
    SYNTAX Unsigned32
    MAX-ACCESS read-only
    STATUS current
    DESCRIPTION "Count of request parsing"
    ::= { statsCollector 49 }

  requestParsing-Total OBJECT-TYPE
    SYNTAX DisplayString (SIZE(0..32))
    MAX-ACCESS read-only
    STATUS current
    DESCRIPTION "Total time of request parsing"
    ::= { statsCollector 50 }

  requestParsing-Max OBJECT-TYPE
    SYNTAX DisplayString (SIZE(0..32))
    MAX-ACCESS read-only
    STATUS current
    DESCRIPTION "Maximun time of request parsing"
    ::= { statsCollector 51 }

  requestParsing-Min OBJECT-TYPE
    SYNTAX DisplayString (SIZE(0..32))
    MAX-ACCESS read-only
    STATUS current
    DESCRIPTION "Minimum time of request parsing"
    ::= { statsCollector 52 }

  requestParsing-Average OBJECT-TYPE
    SYNTAX DisplayString (SIZE(0..32))
    MAX-ACCESS read-only
    STATUS current
    DESCRIPTION "Average time of request parsing"
    ::= { statsCollector 53 }

  creativeSelection-Count OBJECT-TYPE
    SYNTAX Unsigned32
    MAX-ACCESS read-only
    STATUS current
    DESCRIPTION "Count of creative selection"
    ::= { statsCollector 54 }

  creativeSelection-Total OBJECT-TYPE
    SYNTAX DisplayString (SIZE(0..32))
    MAX-ACCESS read-only
    STATUS current
    DESCRIPTION "Total time of creative selection"
    ::= { statsCollector 55 }

  creativeSelection-Max OBJECT-TYPE
    SYNTAX DisplayString (SIZE(0..32))
    MAX-ACCESS read-only
    STATUS current
    DESCRIPTION "Maximun time of creative selection"
    ::= { statsCollector 56 }

  creativeSelection-Min OBJECT-TYPE
    SYNTAX DisplayString (SIZE(0..32))
    MAX-ACCESS read-only
    STATUS current
    DESCRIPTION "Minimum time of creative selection"
    ::= { statsCollector 57 }

  creativeSelection-Average OBJECT-TYPE
    SYNTAX DisplayString (SIZE(0..32))
    MAX-ACCESS read-only
    STATUS current
    DESCRIPTION "Average time of creative selection on the manager"
    ::= { statsCollector 58 }

  creativeSelectionLocal-Count OBJECT-TYPE
    SYNTAX Unsigned32
    MAX-ACCESS read-only
    STATUS current
    DESCRIPTION "Count of creative selection on the manager"
    ::= { statsCollector 59 }

  creativeSelectionLocal-Total OBJECT-TYPE
    SYNTAX DisplayString (SIZE(0..32))
    MAX-ACCESS read-only
    STATUS current
    DESCRIPTION "Total time of creative selection on the manager"
    ::= { statsCollector 60 }

  creativeSelectionLocal-Max OBJECT-TYPE
    SYNTAX DisplayString (SIZE(0..32))
    MAX-ACCESS read-only
    STATUS current
    DESCRIPTION "Maximun time of creative selection on the manager"
    ::= { statsCollector 61 }

  creativeSelectionLocal-Min OBJECT-TYPE
    SYNTAX DisplayString (SIZE(0..32))
    MAX-ACCESS read-only
    STATUS current
    DESCRIPTION "Minimum time of creative selection on the manager"
    ::= { statsCollector 62 }

  creativeSelectionLocal-Average OBJECT-TYPE
    SYNTAX DisplayString (SIZE(0..32))
    MAX-ACCESS read-only
    STATUS current
    DESCRIPTION "Average time of creative selection on the manager"
    ::= { statsCollector 63 }

END
