-- $Id: SiteUserStat.mib 99481 2012-04-03 14:29:57Z alexandr_kashkirov $

SiteUserStat-MIB DEFINITIONS ::= BEGIN

IMPORTS
  MODULE-IDENTITY, OBJECT-TYPE, Unsigned32 FROM SNMPv2-SMI
  DisplayString FROM SNMPv2-TC
  logGeneralizer FROM LogGeneralizer-MIB;

siteUserStat OBJECT IDENTIFIER ::= { logGeneralizer 141 }

inputTimeAvg OBJECT-TYPE
  SYNTAX DisplayString (SIZE(0..32))
  MAX-ACCESS read-only
  STATUS current
  DESCRIPTION "Average time spent on processing the input directory"
  ::= { siteUserStat 1 }

inputTimeMax OBJECT-TYPE
  SYNTAX DisplayString (SIZE(0..32))
  MAX-ACCESS read-only
  STATUS current
  DESCRIPTION "Max time spent on processing the input directory"
  ::= { siteUserStat 2 }

inputTimeTotal OBJECT-TYPE
  SYNTAX DisplayString (SIZE(0..32))
  MAX-ACCESS read-only
  STATUS current
  DESCRIPTION "Total time spent on processing the input directory"
  ::= { siteUserStat 3 }

inputTimePerFileAvg OBJECT-TYPE
  SYNTAX DisplayString (SIZE(0..32))
  MAX-ACCESS read-only
  STATUS current
  DESCRIPTION "Average time spent on processing an input file"
  ::= { siteUserStat 4 }

inputTimePerFileMax OBJECT-TYPE
  SYNTAX DisplayString (SIZE(0..32))
  MAX-ACCESS read-only
  STATUS current
  DESCRIPTION "Max time spent on processing an input file"
  ::= { siteUserStat 5 }

inputSuccessCount OBJECT-TYPE
  SYNTAX Unsigned32
  MAX-ACCESS read-only
  STATUS current
  DESCRIPTION "Total number of successfully processed input files"
  ::= { siteUserStat 6 }

inputErrorCount OBJECT-TYPE
  SYNTAX Unsigned32
  MAX-ACCESS read-only
  STATUS current
  DESCRIPTION "Total number of input files that the service has failed to process"
  ::= { siteUserStat 7 }

outputTimeAvg OBJECT-TYPE
  SYNTAX DisplayString (SIZE(0..32))
  MAX-ACCESS read-only
  STATUS current
  DESCRIPTION "Average time spent on writing log data to disk or database"
  ::= { siteUserStat 8 }

outputTimeMax OBJECT-TYPE
  SYNTAX DisplayString (SIZE(0..32))
  MAX-ACCESS read-only
  STATUS current
  DESCRIPTION "Max time spent on writing log data to disk or database"
  ::= { siteUserStat 9 }

outputTimeTotal OBJECT-TYPE
  SYNTAX DisplayString (SIZE(0..32))
  MAX-ACCESS read-only
  STATUS current
  DESCRIPTION "Total time spent on writing log data to disk or database"
  ::= { siteUserStat 10 }

outputRecordsAvg OBJECT-TYPE
  SYNTAX DisplayString (SIZE(0..32))
  MAX-ACCESS read-only
  STATUS current
  DESCRIPTION "Average number of log data records written per operation"
  ::= { siteUserStat 11 }

outputRecordsMax OBJECT-TYPE
  SYNTAX Unsigned32
  MAX-ACCESS read-only
  STATUS current
  DESCRIPTION "Max number of log data records written per operation"
  ::= { siteUserStat 12 }

outputRecordsTotal OBJECT-TYPE
  SYNTAX Unsigned32
  MAX-ACCESS read-only
  STATUS current
  DESCRIPTION "Total number of log data records written"
  ::= { siteUserStat 13 }

outputSuccessCount OBJECT-TYPE
  SYNTAX Unsigned32
  MAX-ACCESS read-only
  STATUS current
  DESCRIPTION "Total number of successful write operations"
  ::= { siteUserStat 14 }

outputErrorCount OBJECT-TYPE
  SYNTAX Unsigned32
  MAX-ACCESS read-only
  STATUS current
  DESCRIPTION "Total number of failed write operations"
  ::= { siteUserStat 15 }

END
