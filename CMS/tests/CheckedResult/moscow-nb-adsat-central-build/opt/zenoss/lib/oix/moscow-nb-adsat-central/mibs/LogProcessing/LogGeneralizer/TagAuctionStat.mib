TagAuctionStat-MIB DEFINITIONS ::= BEGIN

IMPORTS
  MODULE-IDENTITY, OBJECT-TYPE, Unsigned32 FROM SNMPv2-SMI
  DisplayString FROM SNMPv2-TC
  logGeneralizer FROM LogGeneralizer-MIB;

tagAuctionStat OBJECT IDENTIFIER ::= { logGeneralizer 138 }

inputTimeAvg OBJECT-TYPE
  SYNTAX DisplayString (SIZE(0..32))
  MAX-ACCESS read-only
  STATUS current
  DESCRIPTION "Average time spent on processing the input directory"
  ::= { tagAuctionStat 1 }

inputTimeMax OBJECT-TYPE
  SYNTAX DisplayString (SIZE(0..32))
  MAX-ACCESS read-only
  STATUS current
  DESCRIPTION "Max time spent on processing the input directory"
  ::= { tagAuctionStat 2 }

inputTimeTotal OBJECT-TYPE
  SYNTAX DisplayString (SIZE(0..32))
  MAX-ACCESS read-only
  STATUS current
  DESCRIPTION "Total time spent on processing the input directory"
  ::= { tagAuctionStat 3 }

inputTimePerFileAvg OBJECT-TYPE
  SYNTAX DisplayString (SIZE(0..32))
  MAX-ACCESS read-only
  STATUS current
  DESCRIPTION "Average time spent on processing an input file"
  ::= { tagAuctionStat 4 }

inputTimePerFileMax OBJECT-TYPE
  SYNTAX DisplayString (SIZE(0..32))
  MAX-ACCESS read-only
  STATUS current
  DESCRIPTION "Max time spent on processing an input file"
  ::= { tagAuctionStat 5 }

inputSuccessCount OBJECT-TYPE
  SYNTAX Unsigned32
  MAX-ACCESS read-only
  STATUS current
  DESCRIPTION "Total number of successfully processed input files"
  ::= { tagAuctionStat 6 }

inputErrorCount OBJECT-TYPE
  SYNTAX Unsigned32
  MAX-ACCESS read-only
  STATUS current
  DESCRIPTION "Total number of input files that the service has failed to process"
  ::= { tagAuctionStat 7 }

outputTimeAvg OBJECT-TYPE
  SYNTAX DisplayString (SIZE(0..32))
  MAX-ACCESS read-only
  STATUS current
  DESCRIPTION "Average time spent on writing log data to disk or database"
  ::= { tagAuctionStat 8 }

outputTimeMax OBJECT-TYPE
  SYNTAX DisplayString (SIZE(0..32))
  MAX-ACCESS read-only
  STATUS current
  DESCRIPTION "Max time spent on writing log data to disk or database"
  ::= { tagAuctionStat 9 }

outputTimeTotal OBJECT-TYPE
  SYNTAX DisplayString (SIZE(0..32))
  MAX-ACCESS read-only
  STATUS current
  DESCRIPTION "Total time spent on writing log data to disk or database"
  ::= { tagAuctionStat 10 }

outputRecordsAvg OBJECT-TYPE
  SYNTAX DisplayString (SIZE(0..32))
  MAX-ACCESS read-only
  STATUS current
  DESCRIPTION "Average number of log data records written per operation"
  ::= { tagAuctionStat 11 }

outputRecordsMax OBJECT-TYPE
  SYNTAX Unsigned32
  MAX-ACCESS read-only
  STATUS current
  DESCRIPTION "Max number of log data records written per operation"
  ::= { tagAuctionStat 12 }

outputRecordsTotal OBJECT-TYPE
  SYNTAX Unsigned32
  MAX-ACCESS read-only
  STATUS current
  DESCRIPTION "Total number of log data records written"
  ::= { tagAuctionStat 13 }

outputSuccessCount OBJECT-TYPE
  SYNTAX Unsigned32
  MAX-ACCESS read-only
  STATUS current
  DESCRIPTION "Total number of successful write operations"
  ::= { tagAuctionStat 14 }

outputErrorCount OBJECT-TYPE
  SYNTAX Unsigned32
  MAX-ACCESS read-only
  STATUS current
  DESCRIPTION "Total number of failed write operations"
  ::= { tagAuctionStat 15 }

END
